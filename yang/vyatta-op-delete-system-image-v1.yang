module vyatta-op-delete-system-image-v1 {
	namespace "urn:vyatta.com:mgmt:vyatta-op-delete-system-image:1";
	prefix vyatta-op-delete-system-image-v1;

	import vyatta-opd-extensions-v1 {
		prefix opd;
	}
	import vyatta-op-delete-v1 {
		prefix delete;
	}
	import vyatta-op-delete-system-v1 {
		prefix system;
	}

	organization "AT&T Inc.";
	contact
		"AT&T
		 Postal: 208 S. Akard Street
				 Dallas, TX 25202
		 Web: www.att.com";

	description
		"Copyright (c) 2019, AT&T Intellectual Property.
		 All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		Defines the top level 'image' level under 'delete system' for operational CLI";

	revision 2019-02-15 {
		description "Initial version";
	}

	opd:augment /delete:delete/system:system {
		opd:command image {
			opd:help "Remove an installed image from the system";
			opd:on-enter 'vyatta-image-op --action=delete-image-prompt';

			opd:argument system-image {
				opd:help "Name of image to delete";
				opd:allowed "vyatta-image-op --action=list-images";
				opd:on-enter 'vyatta-image-op --action=delete-image "$4"';
				type string;
			}	
		}
	}
}
