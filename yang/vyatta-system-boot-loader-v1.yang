module vyatta-system-boot-loader-v1 {
	namespace "urn:vyatta.com:mgmt:vyatta-system-boot-loader:1";
	prefix vyatta-system-boot-loader-v1;

	import vyatta-system-v1 {
		prefix system;
	}
	import configd-v1 {
		prefix configd;
	}

	organization "AT&T Inc.";
	contact
		"AT&T
		 Postal: 208 S. Akard Street
				 Dallas, TX 25202
		 Web: www.att.com";

	description
		"Copyright (c) 2018-2019, AT&T Intellectual Property.
		 All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		Boot loader login configuration";

	revision 2018-08-05 {
		description "Adds minimum password requirement in plaintext_pass syntax validate.
        Simplifies encrypted password regex as yang pattern does not support extended regex.";
	}
	revision 2018-01-19 {
		description "Initial revision of version 1.";
	}
	augment /system:system {
		container boot-loader {
			configd:help "Boot loader configuration";
			description "Configuration container for the system boot loader.";
			configd:end "/opt/vyatta/sbin/vyatta_update_grub.pl --generate-grub";
			list user {
				configd:help "Boot loader users";
				description "A list of users allowed to change boot loader configuration.";
				key "user-id";
				leaf user-id {
					type string;
					configd:help "User login";
					description "The boot loader user node.";
				}
				leaf encrypted-password {
					type string {
						pattern 'grub\.pbkdf2\.sha512\.10000\.[A-F0-9][A-F0-9]*\.[A-F0-9][A-F0-9]*' {
							configd:error-message "Not a valid encrypted password for user $VAR(../@)";
						}
					}
					description "A grub pbkdf2 encrypted password.";
					configd:secret "true";
					configd:help "Encrypted password";
					mandatory true;
				}
				leaf plaintext-password {
					type string {
						length 1..64;
						configd:syntax "/opt/vyatta/share/tmplscripts/system/boot-loader/plaintext-password/configd_validate1.cli";
					}
					description "Converts a plaintext-password to a pbkdf2 and stores it in ../encrypted-password/@";
					configd:secret "true";
					configd:subst "/opt/vyatta/share/tmplscripts/system/boot-loader/plaintext-password/configd_subst1.cli";
					configd:help "Plaintext password for encryption. Passwords must adhere to the system password requirements.";
				}
			}
		}
	}
}
