module vyatta-op-clone-system-image-v1 {
	namespace "urn:vyatta.com:mgmt:vyatta-op-clone-system-image:1";
	prefix vyatta-op-clone-system-image-v1;

	import vyatta-opd-extensions-v1 {
		prefix opd;
	}
	import vyatta-op-clone-v1 {
		prefix clone;
	}
	import vyatta-op-clone-system-v1 {
		prefix system;
	}

	organization "AT&T Inc.";
	contact
		"AT&T
		 Postal: 208 S. Akard Street
				 Dallas, TX 25202
		 Web: www.att.com";

	description
		"Copyright (c) 2019, AT&T Intellectual Property.
		 All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		Defines the top level 'image' level under 'clone system' for operational CLI";

	revision 2019-02-15 {
		description "Initial version";
	}

	opd:augment /clone:clone/system:system {
		opd:command image {
			opd:help "Clone a system image";

			opd:argument system-image {
				opd:help "Name of local or remote image to clone";
				opd:allowed 'vyatta-image-op --action=list-images &&
					echo -n "<user>@<host>:<image-name>"';
				type string;
				
				opd:argument new-system-image {
					opd:help "New name for cloned system image";
					opd:allowed "echo '<cloned-image-name>'";
					opd:privileged true;
					opd:on-enter 'clone-image.pl --old_name "$4" \
						--new_name "$5"';
					type string;

					opd:command clean {
						opd:help "Don't clone the read-write copy of the image";
						opd:privileged true;
						opd:on-enter 'clone-image.pl --old_name "$4" \
							--new_name "$5" --no_rw';
					}
				}
			}
		}
	}
}
