module vyatta-image-v1 {
	namespace "urn:vyatta.com:mgmt:vyatta-image:1";
	prefix image-v1;

	import configd-v1 { prefix configd; }

	organization "Brocade Communications Systems, Inc.";
	contact
		"Brocade Communications Systems, Inc.
                 Postal: 130 Holger Way
                         San Jose, CA 95134
                 E-mail: support@Brocade.com
                 Web: www.brocade.com";

	description
		"Copyright (c) 2019, AT&T Intellectual Property.
	        All rights reserved.

		Copyright (c) 2017 by Brocade Communications Systems, Inc.
	        All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

        	The YANG module for vyatta-image-v1";

	revision 2016-12-21 {
		description "Initial revision";
	}

	container system-image {
		config false;
		configd:get-state "vyatta-image-rpc --action=get-state";
		list installed-images {
			description "The images currently installed on the system";
			key name;
			leaf name {
				description "The user supplied name of the image";
				type string;
			}
			leaf version {
				description "The version of the OS installed in the image";
				type string;
			}
			container storage {
				leaf total {
					description
						"The total amount of storage the image requires
					in bytes";
					type uint64;
					units "bytes";
				}
				leaf read-only {
					description
						"The size of the immutable portion
					of the image in bytes";
					type uint64;
					units "bytes";
				}
				leaf read-write {
					description
						"The size of the mutable portion
					of the image in bytes";
					type uint64;
					units "bytes";
				}
			}
		}
		leaf running-image {
			description
				"The name of the image that is currently
			running on the system";
			type string;
		}
		leaf default-boot-image {
			description
				"The name of the image that will be booted
			by default when the system starts up";
			type string;
		}
	}

	rpc add-image {
		description "Add a new system image";
		input {
			leaf location {
				description
					"The name of the image, this may be a local path or a URL";
				mandatory true;
				type string;
			}
			leaf username {
				description
					"The username for the location in which
				the image is stored";
				must "../password" {
					error-message "Password must be supplied with username";
				}
				type string {
					length "1..max";
				}
			}
			leaf password {
				description
					"The password for the location in which
				the image is stored";
				must "../username" {
					error-message "Username must be supplied with password";
				}
				type string {
					length "1..max";
				}
			}
		}
		configd:call-rpc "vyatta-image-rpc --action=add-image";
	}

	rpc delete-image {
		description "Delete an existing image";
		input {
			leaf name {
				description "Name of the image";
				mandatory true;
				type string;
			}
		}
		configd:call-rpc "vyatta-image-rpc --action=delete-image";
	}

	rpc set-default-boot-image {
		description
			"Set the image that will be booted by default when
		the system starts up";
		input {
			leaf name {
				description "Name of the image";
				mandatory true;
				type string;
			}
		}
		configd:call-rpc "vyatta-image-rpc --action=set-default-boot-image";
	}
}
